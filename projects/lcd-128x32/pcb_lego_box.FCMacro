"""
PCB 樂高卡扣盒 v8 — FreeCAD Macro
====================================
v8 變更：
  - LEGO_RI 從 2.4mm → 2.5mm（直徑 +0.2mm）
    補償 PETG 收縮，解決榫頭深處過緊問題
v7 變更：
  - 底板加厚 1.5mm：新增 FLOOR_T=3.5mm（側牆仍 WALL=2mm）
  - BOX_D 從 10mm 增至 11.5mm，保持內腔深度 8mm 不變
  - 樂高孔仍貫穿底板（CYL_H=4.6 > FLOOR_T=3.5）
v6 變更：
  - 短邊牆（X=0 / X=ot_l）頂部 U 形缺口（從頂緣切除 1.8mm）
    左右各留 CONN_SIDE_GAP=4mm，開口向上開放
v5 變更：
  - 四角楔塊加寬至 4×4mm（圓角 PCB 支撐更穩）
  - 新增 WEDGE_DROP=1.5mm：楔塊頂部往下降，增加 PCB 厚度公差
v4 變更：
  - 圓柱管高度改為 4.6mm（給 PCB 背面零件留 3.8mm 空間）
  - 移除全寬橫肋，改為四角楔塊支撐 PCB 底面
  - 樂高孔貫穿修正：先 fuse 外管，再 cut 內孔
"""

import FreeCAD, Part
from FreeCAD import Vector

doc = FreeCAD.newDocument("PCB_LegoBox_v8")

# ─── 可調參數 ──────────────────────────────────────────────
PCB_L     = 48.0   # PCB 長邊 (mm) — X 方向
PCB_W     = 24.0   # PCB 短邊 (mm) — Y 方向
PCB_T     = 1.6    # PCB 厚度
BOX_D     = 11.5   # 盒深（底板加厚後補高，Z=0 到開口 Z=BOX_D）
WALL      = 2.0    # 側壁厚
FLOOR_T   = WALL + 1.5  # 底板厚度（3.5mm，比側壁厚 1.5mm）
CLEAR     = 0.3    # PCB 每邊間隙

# 樂高圓柱管
LEGO_P    = 8.0    # 孔間距
LEGO_RI   = 2.5    # 內孔半徑（直徑 5.0mm，+0.2mm 補償 PETG 收縮）
LEGO_RO   = 3.0    # 外管半徑（直徑 6mm）
LEGO_ROWS = 3
LEGO_COLS = 3
CYL_H     = 4.6    # 圓柱高度（從 Z=0，給 PCB 背面零件留空）

# 四角楔塊（支撐 PCB 底面）
CORNER_W   = 4.0   # 楔塊 XY 尺寸（v5: 4mm，適合圓角 PCB）
WEDGE_DROP = 1.5   # 楔塊頂部往下降（增加 PCB 厚度公差）

# 短邊接頭開孔
CONN_SIDE_GAP = 4.0   # 距短邊側壁距離（Y 方向，左右各留）
CONN_TOP_GAP  = 1.8   # 距上緣距離（Z 方向，保留頂部唇邊）

# 卡扣（長邊中央，slot 式）
CLIP_W    = 10.0   # 舌片寬度（X 方向）
LIP_D     = 1.0    # 唇口往內凸出（Y 方向）
LIP_H     = 1.5    # 唇口高度（Z 方向）
SLOT_W    = 0.8    # slot 寬度（X 方向）
SLOT_D    = 5.0    # slot 深度（Z 方向）
# ──────────────────────────────────────────────────────────

in_l     = PCB_L + 2*CLEAR      # 內腔長 = 48.6mm
in_w     = PCB_W + 2*CLEAR      # 內腔寬 = 24.6mm
ot_l     = in_l + 2*WALL        # 外殼長 = 52.6mm
ot_w     = in_w + 2*WALL        # 外殼寬 = 28.6mm
pcb_z    = BOX_D - PCB_T               # PCB 底面設計 Z = 9.9mm
corner_h = pcb_z - FLOOR_T - WEDGE_DROP  # 楔塊高度 = 4.9mm

# ─── 1. 外殼 ────────────────────────────────────────────────
outer  = Part.makeBox(ot_l, ot_w, BOX_D)
cavity = Part.makeBox(in_l, in_w, BOX_D - FLOOR_T, Vector(WALL, WALL, FLOOR_T))
body   = outer.cut(cavity)

# ─── 2. 樂高圓柱管（3×3，高 4.6mm）─────────────────────────
# 先 fuse 外管（加材料），再 cut 內孔（減材料，確保孔貫穿背板）
bcx = ot_l / 2
bcy = ot_w / 2
for r in range(LEGO_ROWS):
    for c in range(LEGO_COLS):
        hx = bcx + (c - (LEGO_COLS-1)/2) * LEGO_P
        hy = bcy + (r - (LEGO_ROWS-1)/2) * LEGO_P
        ocyl = Part.makeCylinder(LEGO_RO, CYL_H, Vector(hx, hy, 0), Vector(0,0,1))
        body = body.fuse(ocyl)
        icyl = Part.makeCylinder(LEGO_RI, CYL_H + 0.2, Vector(hx, hy, -0.1), Vector(0,0,1))
        body = body.cut(icyl)

# ─── 3. 四角楔塊（內腔四角，PCB 底面落在楔塊頂面）────────────
corners = [
    Vector(WALL,                WALL,                FLOOR_T),   # 左下角
    Vector(WALL,                ot_w-WALL-CORNER_W,  FLOOR_T),   # 左上角
    Vector(ot_l-WALL-CORNER_W,  WALL,                FLOOR_T),   # 右下角
    Vector(ot_l-WALL-CORNER_W,  ot_w-WALL-CORNER_W,  FLOOR_T),  # 右上角
]
for pos in corners:
    blk  = Part.makeBox(CORNER_W, CORNER_W, corner_h, pos)
    body = body.fuse(blk)

# ─── 4. 卡扣（兩條長邊中央，slot 式 snap-fit）──────────────
mx   = ot_l / 2
lx0  = mx - CLIP_W/2
lx1  = mx + CLIP_W/2

# 唇口（只在開口頂端，下方完全平整）
lip_a = Part.makeBox(CLIP_W, LIP_D, LIP_H, Vector(lx0, WALL,              BOX_D-LIP_H))
lip_b = Part.makeBox(CLIP_W, LIP_D, LIP_H, Vector(lx0, ot_w-WALL-LIP_D,  BOX_D-LIP_H))
body  = body.fuse(lip_a).fuse(lip_b)

# Slot（切穿兩側壁，讓舌片可向外彈）
sL_a = Part.makeBox(SLOT_W, WALL+0.2, SLOT_D, Vector(lx0-SLOT_W, -0.1,           BOX_D-SLOT_D))
sR_a = Part.makeBox(SLOT_W, WALL+0.2, SLOT_D, Vector(lx1,         -0.1,           BOX_D-SLOT_D))
sL_b = Part.makeBox(SLOT_W, WALL+0.2, SLOT_D, Vector(lx0-SLOT_W,  ot_w-WALL-0.1, BOX_D-SLOT_D))
sR_b = Part.makeBox(SLOT_W, WALL+0.2, SLOT_D, Vector(lx1,          ot_w-WALL-0.1, BOX_D-SLOT_D))
body  = body.cut(sL_a).cut(sR_a).cut(sL_b).cut(sR_b)

# ─── 5. 短邊頂部缺口（左右兩面，各留 4mm 側邊，從頂緣切除 1.8mm）─
conn_w = ot_w - 2 * CONN_SIDE_GAP           # 缺口寬 Y = 20.6mm
# 從頂部往下切 CONN_TOP_GAP=1.8mm，缺口向上開放（U 形）
cut_short_l = Part.makeBox(WALL+0.2, conn_w, CONN_TOP_GAP,
                            Vector(-0.1, CONN_SIDE_GAP, BOX_D-CONN_TOP_GAP))
cut_short_r = Part.makeBox(WALL+0.2, conn_w, CONN_TOP_GAP,
                            Vector(ot_l-WALL-0.1, CONN_SIDE_GAP, BOX_D-CONN_TOP_GAP))
body = body.cut(cut_short_l).cut(cut_short_r)

# ─── 6. 加入文件 ───────────────────────────────────────────
feat = doc.addObject("Part::Feature", "PCB_LegoBox_v8")
feat.Shape = body
doc.recompute()

try:
    import FreeCADGui
    FreeCADGui.SendMsgToActiveView("ViewFit")
    FreeCADGui.activeDocument().activeView().viewIsometric()
except Exception:
    pass

print("=" * 54)
print(f"  外殼      : {ot_l:.1f} x {ot_w:.1f} x {BOX_D:.1f} mm")
print(f"  底板厚度  : {FLOOR_T:.1f}mm（側壁 {WALL}mm）")
print(f"  內腔深度  : {BOX_D-FLOOR_T:.1f}mm")
print(f"  圓柱管    : ∅{LEGO_RO*2:.0f}mm / ∅{LEGO_RI*2:.0f}mm，高 {CYL_H}mm（貫穿底板 ✓）")
print(f"  PCB 背面  : {pcb_z - CYL_H:.1f}mm 零件空間（Z={CYL_H}～{pcb_z:.1f}）")
print(f"  四角楔塊  : {CORNER_W}×{CORNER_W}mm，高 {corner_h:.1f}mm，頂面 Z={FLOOR_T+corner_h:.1f}")
print(f"  卡扣空間  : {BOX_D-LIP_H-(FLOOR_T+corner_h):.1f}mm（楔塊頂 Z={FLOOR_T+corner_h:.1f} → 唇口底 Z={BOX_D-LIP_H:.1f}）")
print(f"  短邊缺口  : {conn_w:.1f}mm 寬，頂部切 {CONN_TOP_GAP}mm（Z={BOX_D-CONN_TOP_GAP:.1f}～{BOX_D:.1f}，側留 {CONN_SIDE_GAP}mm）")
print("=" * 54)
print("建議：PETG，開口朝上，無需支撐")
