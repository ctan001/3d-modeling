# -*- coding: utf-8 -*-
# keycap_enter_1u_v2.FCMacro
# v2 變更：頂面【全平】（v1 碗面頂面朝下列印中心懸空下垂、拉絲 -> 改平頂）
# 全平頂 1U 鍵帽 + Cherry MX 十字軸 + 回車折返箭頭(獨立黑色實體)
# 列印方向：頂面朝下、免支撐；平頂貼板 -> 鏡面光滑、黑字第一層最清晰
# 專案：鍵帽專案 / Action 2026-06-15_Cherry鍵帽
import os
import FreeCAD as App
import Part
try:
    import FreeCADGui as Gui
except Exception:
    Gui = None

# ============ 參數 ============
BASE      = 18.2   # 底部 footprint (1U)
TOP       = 13.5   # 頂部 footprint
H         = 8.0    # 鍵帽高度
WALL      = 1.5    # 壁厚
CORNER_R  = 1.5    # 邊角圓角
CEIL_Z    = 5.5    # 內腔頂 -> 平頂天花板厚 = H-CEIL_Z = 2.5mm
LEG_DEPTH = 1.0    # 字凹陷深度(=黑字厚)

BOSS_R    = 2.75; BOSS_H = 4.0          # MX 軸座 Ø5.5 高4
CROSS_L   = 4.1;  CROSS_W = 1.3         # 十字孔(太緊改 1.35)

def rect_wire(w, z):
    h = w/2.0
    p = [App.Vector(-h,-h,z),App.Vector(h,-h,z),App.Vector(h,h,z),App.Vector(-h,h,z),App.Vector(-h,-h,z)]
    return Part.makePolygon(p)
def box(x0,y0,x1,y1,z0,z1):
    return Part.makeBox(x1-x0,y1-y0,z1-z0,App.Vector(x0,y0,z0))

# 1. 外殼梯台 + 圓角（頂面全平，不再切碗）
cap = Part.makeLoft([rect_wire(BASE,0.0), rect_wire(TOP,H)], True)
ce = [e for e in cap.Edges if e.BoundBox.ZLength > 1.0]
try: cap = cap.makeFillet(CORNER_R, ce)
except Exception as e: App.Console.PrintWarning("圓角失敗: %s\n"%e)

# 2. 中空
inner = Part.makeLoft([rect_wire(BASE-2*WALL,-0.1), rect_wire(TOP-2*WALL,CEIL_Z)], True)
cap = cap.cut(inner)

# 3. MX 十字軸
boss = Part.makeCylinder(BOSS_R, BOSS_H, App.Vector(0,0,CEIL_Z-BOSS_H))
cap = cap.fuse(boss)
cz0,cz1 = CEIL_Z-BOSS_H-0.2, CEIL_Z+0.01
cross = box(-CROSS_L/2,-CROSS_W/2,CROSS_L/2,CROSS_W/2,cz0,cz1).fuse(
        box(-CROSS_W/2,-CROSS_L/2,CROSS_W/2,CROSS_L/2,cz0,cz1))
cap = cap.cut(cross)

# 4. 回車折返箭頭(獨立實體) — 頂面下 LEG_DEPTH 平板切片 ∩ 箭頭
zlo,zhi = 4.5,9.0
riser = box(1.6,-1.8,3.2,2.6,zlo,zhi)
shaft = box(-2.0,-1.8,3.2,-0.2,zlo,zhi)
htip = [App.Vector(-3.4,-1.0,zlo),App.Vector(-1.6,-2.8,zlo),App.Vector(-1.6,0.8,zlo),App.Vector(-3.4,-1.0,zlo)]
head = Part.Face(Part.makePolygon(htip)).extrude(App.Vector(0,0,zhi-zlo))
arrow = riser.fuse(shaft).fuse(head)

slab = box(-TOP, -TOP, TOP, TOP, H-LEG_DEPTH, H+0.1)   # 頂面下 1mm 平板
legend = slab.common(arrow).common(cap)
body   = cap.cut(legend)

# 5. 文件 + 上色
doc = App.newDocument("keycap_enter_1u_v2")
bo = doc.addObject("Part::Feature","Keycap_Body_White"); bo.Shape = body
lo = doc.addObject("Part::Feature","Legend_Black");      lo.Shape = legend
if Gui:
    try:
        bo.ViewObject.ShapeColor=(0.95,0.95,0.95); lo.ViewObject.ShapeColor=(0.10,0.10,0.10)
    except Exception: pass
doc.recompute()

# 6. 匯出
OUT = "C:/Users/ctan0/Claude AI/100_Projects/active/鍵帽專案/cad"
os.makedirs(OUT, exist_ok=True)
try:
    import MeshPart
    for shp,name in [(body,"keycap_enter_body_v2"),(legend,"keycap_enter_legend_v2")]:
        m = MeshPart.meshFromShape(Shape=shp, LinearDeflection=0.04, AngularDeflection=0.15)
        m.write(os.path.join(OUT, name+".stl"))
except Exception as e: App.Console.PrintError("STL失敗: %s\n"%e)
try: doc.saveAs(os.path.join(OUT,"keycap_enter_1u_v2.FCStd"))
except Exception as e: App.Console.PrintWarning("FCStd失敗: %s\n"%e)
if Gui:
    try:
        Gui.activeDocument().activeView().viewIsometric(); Gui.SendMsgToActiveView("ViewFit")
    except Exception: pass
App.Console.PrintMessage("v2完成 body vol=%.1f legend vol=%.1f\n"%(body.Volume, legend.Volume))
