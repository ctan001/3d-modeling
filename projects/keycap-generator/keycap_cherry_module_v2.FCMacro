# -*- coding: utf-8 -*-
# keycap_cherry_module_v2.FCMacro  —  Cherry Key 設計模組（基準, v2）
# 帽體幾何 = v2 實印驗證版（全平頂 1U + MX 十字軸，頂面朝下免支撐），勿動。
# v2 新增字型 builder：ctrl_enter(大C內嵌鈍角箭頭)、voice_wave(5條音波)。
# 已過 Codex 列印可行性檢查(0.4噴頭/0.16層)：筆寬>=1.0、雙色間隙>=1.0。
# 【做新 Cherry Key 只改 JOBS 與字型 builder】
import os
import FreeCAD as App
import Part
try:
    import FreeCADGui as Gui
except Exception:
    Gui = None

# ===== 帽體參數（鎖定）=====
BASE=18.2; TOP=13.5; H=8.0; WALL=1.5; CORNER_R=1.5
CEIL_Z=5.5; LEG_DEPTH=1.0
BOSS_R=2.75; BOSS_H=4.0; CROSS_L=4.1; CROSS_W=1.3
ZLO, ZHI = 4.5, 9.0
OUT="C:/Users/ctan0/Claude AI/100_Projects/active/鍵帽專案/cad"

# ====== 要產生的鍵（只改這裡）======
JOBS = [
    ("ctrl_enter", "ctrl_enter"),   # Ctrl+Enter
    ("voice",      "voice_wave"),   # 語音輸入
]
TEXT="A"; FONT="C:/Windows/Fonts/arialbd.ttf"; FONT_SIZE=7.0   # text 模式用

def rect_wire(w,z):
    h=w/2.0
    return Part.makePolygon([App.Vector(-h,-h,z),App.Vector(h,-h,z),App.Vector(h,h,z),App.Vector(-h,h,z),App.Vector(-h,-h,z)])
def box(x0,y0,x1,y1,z0,z1):
    return Part.makeBox(x1-x0,y1-y0,z1-z0,App.Vector(x0,y0,z0))

# ---------- 帽體（每次重建，便宜）----------
def build_cap():
    cap = Part.makeLoft([rect_wire(BASE,0.0),rect_wire(TOP,H)],True)
    ce=[e for e in cap.Edges if e.BoundBox.ZLength>1.0]
    try: cap=cap.makeFillet(CORNER_R,ce)
    except Exception as e: App.Console.PrintWarning("圓角失敗:%s\n"%e)
    cap=cap.cut(Part.makeLoft([rect_wire(BASE-2*WALL,-0.1),rect_wire(TOP-2*WALL,CEIL_Z)],True))
    cap=cap.fuse(Part.makeCylinder(BOSS_R,BOSS_H,App.Vector(0,0,CEIL_Z-BOSS_H)))
    cz0,cz1=CEIL_Z-BOSS_H-0.2,CEIL_Z+0.01
    cap=cap.cut(box(-CROSS_L/2,-CROSS_W/2,CROSS_L/2,CROSS_W/2,cz0,cz1).fuse(
                box(-CROSS_W/2,-CROSS_L/2,CROSS_W/2,CROSS_L/2,cz0,cz1)))
    return cap

# ---------- 字型 builder（回傳貫穿頂部的柱）----------
def b_arrow_return():
    a=box(1.6,-1.8,3.2,2.6,ZLO,ZHI).fuse(box(-2.0,-1.8,3.2,-0.2,ZLO,ZHI))
    head=Part.Face(Part.makePolygon([App.Vector(-3.4,-1.0,ZLO),App.Vector(-1.6,-2.8,ZLO),
            App.Vector(-1.6,0.8,ZLO),App.Vector(-3.4,-1.0,ZLO)])).extrude(App.Vector(0,0,ZHI-ZLO))
    return a.fuse(head)

def b_ctrl_enter():
    Ro,Ri=5.5,3.5
    ring=Part.makeCylinder(Ro,ZHI-ZLO,App.Vector(0,0,ZLO)).cut(
          Part.makeCylinder(Ri,ZHI-ZLO+0.2,App.Vector(0,0,ZLO-0.1)))
    ring=ring.cut(box(0.6,-2.2,Ro+1.0,2.2,ZLO-0.1,ZHI+0.1))      # 右開口
    sh=box(-1.6,-1.55,1.4,-0.45,ZLO,ZHI)                          # 水平筆
    ri=box(0.3,-1.0,1.4,1.6,ZLO,ZHI)                             # 直筆(往上)
    head=Part.Face(Part.makePolygon([App.Vector(-1.3,0.0,ZLO),App.Vector(-1.3,-2.0,ZLO),
            App.Vector(-2.3,-1.25,ZLO),App.Vector(-2.3,-0.75,ZLO),App.Vector(-1.3,0.0,ZLO)])
          ).extrude(App.Vector(0,0,ZHI-ZLO))                      # 鈍頭
    arrow=sh.fuse(ri).fuse(head); arrow.translate(App.Vector(0.3,0,0))
    return ring.fuse(arrow)

def b_voice_wave():
    W=1.2; r=W/2.0
    cxs=[-4.6,-2.3,0.0,2.3,4.6]; Hs=[3.2,6.4,8.0,5.2,3.6]
    out=None
    for cx,Hh in zip(cxs,Hs):
        yb=Hh/2.0
        bar=box(cx-r,-yb+r,cx+r,yb-r,ZLO,ZHI)
        bar=bar.fuse(Part.makeCylinder(r,ZHI-ZLO,App.Vector(cx, yb-r,ZLO)))
        bar=bar.fuse(Part.makeCylinder(r,ZHI-ZLO,App.Vector(cx,-yb+r,ZLO)))
        out = bar if out is None else out.fuse(bar)
    return out

def b_text(doc):
    import Draft
    ss=Draft.make_shapestring(String=TEXT,FontFile=FONT,Size=FONT_SIZE); doc.recompute()
    shp=ss.Shape.copy(); doc.removeObject(ss.Name)
    bb=shp.BoundBox
    shp.translate(App.Vector(-(bb.XMin+bb.XLength/2.0),-(bb.YMin+bb.YLength/2.0),-bb.ZMin+ZLO))
    return shp.extrude(App.Vector(0,0,ZHI-ZLO))

BUILDERS={"arrow_return":b_arrow_return,"ctrl_enter":b_ctrl_enter,"voice_wave":b_voice_wave}

def make_key(name, mode):
    cap=build_cap()
    doc=App.newDocument("keycap_%s_v1"%name)
    prism = b_text(doc) if mode=="text" else BUILDERS[mode]()
    legend=box(-TOP,-TOP,TOP,TOP,H-LEG_DEPTH,H+0.1).common(prism).common(cap)
    body=cap.cut(legend)
    bo=doc.addObject("Part::Feature","Keycap_Body_White"); bo.Shape=body
    lo=doc.addObject("Part::Feature","Legend_Black");      lo.Shape=legend
    if Gui:
        try: bo.ViewObject.ShapeColor=(0.95,0.95,0.95); lo.ViewObject.ShapeColor=(0.10,0.10,0.10)
        except Exception: pass
    doc.recompute()
    os.makedirs(OUT,exist_ok=True)
    try:
        import MeshPart
        for shp,nm in [(body,"keycap_%s_body"%name),(legend,"keycap_%s_legend"%name)]:
            MeshPart.meshFromShape(Shape=shp,LinearDeflection=0.04,AngularDeflection=0.15).write(os.path.join(OUT,nm+".stl"))
    except Exception as e: App.Console.PrintError("STL失敗:%s\n"%e)
    try: doc.saveAs(os.path.join(OUT,"keycap_%s_v1.FCStd"%name))
    except Exception as e: App.Console.PrintWarning("FCStd失敗:%s\n"%e)
    App.Console.PrintMessage("[%s] body=%.1f legend=%.1f\n"%(name,body.Volume,legend.Volume))

for nm,md in JOBS:
    make_key(nm,md)
if Gui:
    try: Gui.activeDocument().activeView().viewIsometric(); Gui.SendMsgToActiveView("ViewFit")
    except Exception: pass
